module VHT-segment-routing {
  namespace "http://viettel.com/vht/yang/VHT-segment-routing";
  prefix vht-segment-routing;

  import ietf-inet-types {
    prefix inet;
  }

  organization
    "VHT";
  contact
    "Viettel";
  description
    "VHT SR Yang Model";

  revision 2024-05-30 {
    description
      "Created";
  } 

 grouping mcfg-srmpls-sidmap {
    container address-family {
      container ipv4 {
        uses srcfg-srmpls-conn-af;
      }
    }
  }

  grouping srcfg-srmpls-conn-af {
    list prefixes {
      key "ipprefix";
      leaf ipprefix {
        type inet:ipv4-prefix;
      }
      choice label-type {
		description
		  "Type of SID: index or absolute";
        leaf index {
          type uint32 {
            range "0..1048575";
          }
        }
        leaf absolute {
          type uint32 {
            range "0..1048575";
          }
        }
	  }
	  leaf implicit-null {
	    type empty;
	  }
	  leaf n-flag {
		type empty;
	  }
    }
  }
  
  grouping pcc-config-grouping {
    container pce {
      description
        "List of Path Computation Element (PCE) servers";
      list pce-ipv4-list {
        key "address";
        leaf address {
          description
            "IPv4 address of PCE";
          type inet:ipv4-address;
        }
        leaf source-address {
          description
            "IPv4 source address";
          type inet:ipv4-address;
        }
      }
    }
  }
   
  grouping policy-config-grouping {
    container binding-sid {
      description
        "Static binding SID";
      leaf mpls {
        description
          "MPLS label";
        type uint32 {
          range "16..1048575";
        }
      }
    }
    uses candidate-paths-policy-grouping;
    container color-endpoint {
      description
        "Specify color and end-point for policy";
      leaf color {
        description
          "Specify color for policy";
        type uint32 {
          range "1..4294967295";
        }
      }
      leaf end-point {
        description
          "Policy endpoint address";
        type inet:ipv4-address;
      }
    }
  }
  
  grouping candidate-paths-policy-grouping {
    container candidate-paths {
      description
        "Candidate-paths configuration";
      presence "true";
      list preference {
        description
          "Policy path-option preference entry";
        key "preference-value";
        leaf preference-value {
          description
            "Path-option preference";
          type uint32 {
            range "1..65535";
          }
        }
        uses preference-config-policy-grouping;
      }
    }
  }
  
  grouping preference-config-policy-grouping {
    container constraints {
      description
        "Constraints configuration";
      container affinity {
        description
          "Assign affinities to path";
        container exclude-any {
          description
            "Affinity attributes to exclude - presence of at least one excludes link";
          leaf-list name {
            description
              "Affinity color name";
            type string;
          }
        }
        container include-all {
          description
            "Affinity attributes - all must be included";
          leaf-list name {
            description
              "Affinity color name";
            type string;
          }
        }
        container include-any {
          description
            "Affinity attributes - at least one must be included";
          leaf-list name {
            description
              "Affinity color name";
            type string;
          }
        }
      }
	}  
    choice path-choice {
      case dynamic {
        container dynamic {
          description
            "Dynamic configuration";
          presence "true";
          uses dynamic-config-policy-grouping;
        }
      }
      case explicit {
        container explicit {
          description
            "Preconfigured path";
          leaf segment-list {
            description
              "Specify Segment-list";
            type string;
          }
        }
      }
    }
  }
  
  grouping dynamic-config-policy-grouping {
    container pcep {
      container metric {
        description
          "Metric configuration";
        leaf type {
          description
            "Specify metric type configuration";
          type enumeration {
            enum igp {
              description
                "IGP metric type";
            }
            enum te {
              description
                "TE metric type";
            }
            enum delay {
              description
                "Delay metric type";
            }
          }
        }
      }
    }
  }
  grouping segment-list-config-grouping {
    list segment-entry {
      key "index";
      leaf index {
        description
          "Specify the next entry index to add, edit (or delete)";
        type uint32 {
          range "1..4294967295";
        }
      }
      container mpls {
        description
          "MPLS configuration";
        choice sid-type {
          case adjacency {
            leaf adjacency {
              description
                "IPv4 address of MPLS adjacency";
              type inet:ipv4-address;
            }
          }
          case label {
            leaf label {
              description
                "Value of MPLS label";
              type uint32 {
                range "16..1048575";
              }
            }
          }
          case prefix {
            leaf prefix {
              description
                "MPLS prefix configuration";
              type inet:ipv4-address;
              
            }
          }
        }
      }
    }
  }
  
  grouping config-segment-routing-grouping {
    container mpls {
      description
        "Segment Routing MPLS Mode";
      presence "true";
      container connected-prefix-sid-map {
        description
          "Enter Connected Prefix Sid Map  Mode";
        uses mcfg-srmpls-sidmap;
      }
      container global-block {
        description
          "SR Global Block Config";
        leaf range-start {
          description
            "SR GB Label Range Start";
          default "16000";
          type uint32 {
            range "16..1048575";
          }
        }
        leaf range-end {
          description
            "SR GB Label Range End";
          must '. >= ../range-start' {
            error-message "range-end must be greater than or equal to range-start";
          }
          default "23999";
          type uint32 {
            range "16..1048575";
          }
        }
      }
      container local-block {
        description
          "SR Local Block Config";
        leaf range-start {
          description
            "SR LB Label Range Start";
          default "15000";
          type uint32 {
            range "16..1048575";
          }
        }
        leaf range-end {
          description
            "SR LB Label Range End";
          must '. >= ../range-start' {
            error-message "range-end must be greater than or equal to range-start";
          }
          default "15999";
          type uint32 {
            range "16..1048575";
          }
        }
      }
    }
    container traffic-eng {
      description
        "Segment Routing traffic-eng mode";
      presence "true";
      list affinity-map {
        description
          "Affinity-map command mode";
        key "name";
        leaf name {
          description
            "Color name";
          type string;
        }
        leaf bit-position {
          description
            "Bit position";
          type uint8 {
            range "0..31";
          }
        }
      }
      container pcc {
        description
          "Path computation client mode";
        uses pcc-config-grouping;
      }
      list policy {
        description
          "Policy command mode";
        key "name";
        leaf name {
          description
            "Policy name";
          type string;
        }
        uses policy-config-grouping;
      }
      list segment-list {
        description
          "Segment-list configuration";
        key "name";
        leaf name {
          description
            "Identifying name for segment-list";
          type string;
        }
        uses segment-list-config-grouping;
      }
    }
    leaf sr-label-prefer {
      type empty;
    }
  }

  container segment-routing {
    uses config-segment-routing-grouping;
  }
}
