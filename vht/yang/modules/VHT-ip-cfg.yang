module VHT-ip-cfg {
  namespace "http://viettel.com/vht/yang/VHT-ip-cfg";
  prefix vht-ip-cfg;

  import ietf-inet-types {
    prefix inet;
  }

  organization
    "VHT";
  contact
    "Viettel";
  description
    "VHT IP Yang Model";

  revision 2024-05-30 {
    description
      "Created";
  }

  grouping ip-route-grouping-common {
    description
	  "Static route commands on both global and VRF instance";
    list ip-route-static {
      key "prefix mask";
      leaf prefix {
	    description
          "Prefix of static route";
        type inet:ipv4-address;
      }
      leaf mask {
        type uint8 {
          range "0..32";
        }
      }
      leaf out-if {
        description
          "Specify outgoing interface name";
        type union {
          type enumeration {
            enum Null;   //pseudo-interface Null
          }
          type string;
        }
      }
      leaf next-hop-ip-add {
	    description
	      "IP of next hop";
        type inet:ipv4-address;
      }
      leaf metric {
        type uint8 {
          range "1..255";
        }
        default "1";
      }
      leaf description {
        description
          "Description of static route";
        type string;
      }
      leaf tag {
        description
          "Set tag for this route";
        type uint32 {
          range "1..4294967295";
        }
      }
    }
  }

  grouping ip-route-grouping-global {
    uses ip-route-grouping-common;
    leaf segment-routing-policy {
      description
        "Name of segment-routing policy - currently only support on Global instance";
      type string;
    }	
  }

  container ip {
    description
      "Global IP configuration subcommands";
	container route {
	  uses ip-route-grouping-global;
	  list vrf {
	    description
		  "Static route in VRF instance";
		key "name";
		leaf name {
		  description
		    "Name of VRF";
		  type string;
		}
		uses ip-route-grouping-common;
	  }
	}
  }
}
